-- ATIS-0700005.v002.2017 LAES for 3GPP IMS-based VoIP and other Multimedia Services Abstract Syntax v2.0

-- IMS 3GPP VoIP Communication Content Delivery Module

IMS-3GPP-VoIP-CC-Module-v2
{iso(1) identified-organization(3) dod(6) internet(1) private(4) enterprise(1) atis(30613) wtsc(5) ims-voip(2) cc-voip(1) version-3(0)}

DEFINITIONS IMPLICIT TAGS ::=

BEGIN

IMPORTS

-- Imports from ATIS-1000678.v3.2015 Module

CC-APDU 

FROM CCDeliveryHeaderModule-v3
{iso(1) member-body(2) us(840) tia(113737) laes(2) t1(1) t1-678(0) ccdeliveryheader(1) version-5(4)};


-- Notations for IMS-3GPP-VoIP-CC-Module

ims-3GPP-VoIP-CC-Module-OID   OBJECT IDENTIFIER  ::= {iso(1) identified-organization(3) dod(6) internet(1) private(4) enterprise(1) atis(30613) wtsc(5) ims-voip(2) cc-voip(1) version-3(0)}

IMS-3GPP-VoIP-CCProtocol ::= SEQUENCE
{
	ims-3GPP-VoIP-CC-Module-OID	[0]	OBJECT IDENTIFIER,
	ims-3GPP-VoIP-CC-APDU  		[1]	CC-APDU
}

END -- of IMS-3GPP-VoIP-CC-Module
